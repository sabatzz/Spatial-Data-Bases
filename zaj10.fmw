FME workspace zaj10.fmw
Startup Python:
      import smtplib
      from datetime import datetime

      smtp_server = 'smtp.gmail.com'
      port = 465
      sender_email = "$(e-mail)"
      receiver_email = "$(e-mail)"
      password = "$(haslo)"
      current_datetime = datetime.now().strftime('%Y-%m-%d %H:%M:%S')
      powiat = "$(powiat)"
      start = "$(start)"

      message = """\
      Subject: FME start

      Drogi uzytkowniku {}, o godzinie {} rozpoczeto przetwarzanie
      danych dla powiatu {}.
      """.format(receiver_email, current_datetime, powiat)


      try:
          server = smtplib.SMTP_SSL(smtp_server, port)
          server.ehlo()
          server.login(sender_email, password)
          server.sendmail(sender_email, receiver_email, message)
          server.close()

          print('e-mail sent!')

      except Exception as exception:
         print("Error: %s!\n\n" % exception)
Shutdown Python:
      import smtplib
      from datetime import datetime

      smtp_server = 'smtp.gmail.com'
      port = 465
      sender_email = "$(e-mail)"
      receiver_email = "$(e-mail)"
      password = "$(haslo)"
      current_datetime = datetime.now().strftime('%Y-%m-%d %H:%M:%S')
      powiat = "$(powiat)"
      start = "$(start)"

      message = """\
      Subject: FME stop

      Drogi uzytkowniku {}, przetwarzanie
      danych dla powiatu {} zakonczylo sie z sukcesem o godzinie {}.
      """.format(receiver_email, powiat, current_datetime)


      try:
          server = smtplib.SMTP_SSL(smtp_server, port)
          server.ehlo()
          server.login(sender_email, password)
          server.sendmail(sender_email, receiver_email, message)
          server.close()

          print('e-mail sent!')

      except Exception as exception:
         print("Error: %s!\n\n" % exception)

Parameters:
- e-mail = z.sabat02@gmail.com
- e-mail2 = z.sabat02@gmail.com   # e-mail klienta
- start = 20240102000000
- chmury = 30   # max pokrycie chmurami
- powiat = krakowski
- haslo =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
- koniec = 20240102000000
- SourceDataset_SHAPEFILE_3 = $(FME_MF_DIR)powiaty.shp   # Source Esri Shapefile(s)
- SourceDataset_SHAPEFILE = $(FME_MF_DIR)powiaty.shp   # Source Esri Shapefile(s)
- DestDataset_GEOTIFF_5 = $(FME_MF_DIR)FME   # Destination GeoTIFF Folder
- DestDataset_GEOTIFF_4 = $(FME_MF_DIR)FME   # Destination GeoTIFF Folder
- DestDataset_GEOTIFF = $(FME_MF_DIR)FME   # Destination GeoTIFF Folder

Readers:
- SHAPEFILE_1: SHAPEFILE from $(SourceDataset_SHAPEFILE)
- SHAPEFILE_2: SHAPEFILE from $(SourceDataset_SHAPEFILE_3)

Writers:
- GEOTIFF_1: GEOTIFF to $(DestDataset_GEOTIFF)
- GEOTIFF_2: GEOTIFF to $(DestDataset_GEOTIFF_5)
- GEOTIFF_3: GEOTIFF to $(DestDataset_GEOTIFF_4)

powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(JPT_NAZWA_) = powiat $(powiat)",@Value(powiat) = __powiat_
    @Value(powiat) = __powiat_ -> Reprojector
Reprojector
    DEST = EPSG:4326
    INTERPOLATION_TYPE_NAME = Nearest Neighbor
    RASTER_CELL_SIZE = Preserve Cells
    RASTER_TOLERANCE = 0.0
    REPROJECTED -> BoundingBoxAccumulator
BoundingBoxAccumulator
    ACCUM_ATTRS_NAME = Use Attributes From One Feature
    BOUNDING_BOX -> EarthCacheConnector
EarthCacheConnector
    api_key =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
    end_date = 20230731
    interval = 30
    min_aoi_coverage_percentage = 50
    output_id = rgbn-a3e8-11e7-9793-ae4260ee3b4b
    pipeline_name = pipeline5
    start_date = 20230701
    -> Sampler
Sampler
    RATE = 1
    SAMPLE_MODE = Yes
    SAMPLE_TYPE_LONG = First N Features
    SAMPLED -> RasterBandSeparator
RasterBandSeparator
    BAND_INDEX_FIELD = _band_index
    PALETTE_INDEX_FIELD = _palette_index
    RASTER_INDEX_FIELD = _raster_index
    SPLIT_BY_NAME = Band and Palette
    -> RED
    -> NIR
RED: TestFilter
    DEFAULT_VALUE = <UNFILTERED>
    PASSED_TEST_GROUP_OUTPUT = FIRST
    TEST_LIST = "BOOL_OP,OR,COMPOSITE_TEST,""""""1"""""",TEST_CLAUSE,TEST @Value(_band_index) = 0",@Value(_band_index) = 0
    @Value(_band_index) = 0 -> NDVICalculator [Red]
NIR: TestFilter
    DEFAULT_VALUE = <UNFILTERED>
    PASSED_TEST_GROUP_OUTPUT = FIRST
    TEST_LIST = "BOOL_OP,OR,COMPOSITE_TEST,""""""1"""""",TEST_CLAUSE,TEST @Value(_band_index) = 3",@Value(_band_index) = 3
    @Value(_band_index) = 3 -> NDVICalculator [Infrared]
NDVICalculator
    COLORIZE = Blue-Yellow-Green Palette
    INDEXTYPE = NDVI
    SAVIADJUSTMENT = 0.5
    -> RasterStatisticsCalculator
    -> Clipper [CANDIDATE]
RasterStatisticsCalculator
    RASTER_LEVEL = BAND_ONLY
    RASTER_STATS = "0   MEAN   STDEV   "
    -> Statystyka
Statystyka: Inspector
powiaty (reader SHAPEFILE_2)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(JPT_NAZWA_) = powiat $(powiat)",@Value(powiat) = __powiat_
    @Value(powiat) = __powiat_ -> Reprojector_2
Reprojector_2
    DEST = EPSG:4326
    INTERPOLATION_TYPE_NAME = Nearest Neighbor
    RASTER_CELL_SIZE = Preserve Cells
    RASTER_TOLERANCE = 0.0
    REPROJECTED -> Clipper [CLIPPER]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> GEOTIFF (writer GEOTIFF_3)
GEOTIFF (writer GEOTIFF_3)
    attributes: gml_id char(254), JPT_SJR_KO char(254), JPT_POWIER char(254), JPT_KOD_JE char(254), JPT_NAZWA_ char(254), JPT_ORGAN_ char(254), JPT_JOR_ID char(254), WERSJA_OD char(254), WERSJA_DO char(254), WAZNY_OD char(254), WAZNY_DO char(254), JPT_KOD__1 char(254), JPT_NAZWA1 char(254), JPT_ORGAN1 char(254), JPT_WAZNA_ char(254), ID_BUFORA_ char(254), ID_BUFORA1 char(254), ID_TECHNIC char(254), IIP_PRZEST char(254), IIP_IDENTY char(254), IIP_WERSJA char(254), JPT_KJ_IIP char(254), JPT_KJ_I_1 char(254), JPT_KJ_I_2 char(254), JPT_OPIS char(254), JPT_SPS_KO char(254), ID_BUFOR_1 char(254), JPT_ID char(254), JPT_POWI_1 char(254), JPT_KJ_I_3 char(254),
      JPT_GEOMET char(254), JPT_GEOM_1 char(254), SHAPE_LENG char(254), SHAPE_AREA char(254), REGON char(254), RODZAJ char(254)
